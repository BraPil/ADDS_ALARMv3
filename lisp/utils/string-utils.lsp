;;; ADDS String Utilities
(defun adds-str-trim (s / i j)
  (setq i 0 j (1- (strlen s)))
  (while (and (< i j) (= (substr s (1+ i) 1) " ")) (setq i (1+ i)))
  (while (and (> j i) (= (substr s (1+ j) 1) " ")) (setq j (1- j)))
  (substr s (1+ i) (1+ (- j i)))
)

(defun adds-str-upper (s / i result ch)
  (setq result "")
  (setq i 1)
  (while (<= i (strlen s))
    (setq ch (substr s i 1))
    (setq result (strcat result (strcase ch)))
    (setq i (1+ i))
  )
  result
)

(defun adds-str-split (s delim / pos part result)
  (setq result '())
  (while (setq pos (vl-string-search delim s))
    (setq part (substr s 1 pos))
    (setq result (append result (list part)))
    (setq s (substr s (+ pos (strlen delim) 1)))
  )
  (append result (list s))
)

(defun adds-str-replace (s old new / pos)
  (while (setq pos (vl-string-search old s))
    (setq s (strcat (substr s 1 pos) new (substr s (+ pos (strlen old) 1))))
  )
  s
)

(defun adds-format-tag (prefix seq / padded)
  (setq padded (itoa seq))
  (while (< (strlen padded) 4) (setq padded (strcat "0" padded)))
  (strcat prefix "-" padded)
)

(defun adds-validate-tag (tag / valid-chars i ch)
  (setq valid-chars "ABCDEFGHIJKLMNOPQRSTUVWXYZ0123456789-_")
  (setq i 1)
  (setq tag (adds-str-upper tag))
  (while (<= i (strlen tag))
    (setq ch (substr tag i 1))
    (if (not (vl-string-search ch valid-chars))
      (progn (setq i (+ (strlen tag) 1)) (setq tag nil))
    )
    (setq i (1+ i))
  )
  (not (null tag))
)
