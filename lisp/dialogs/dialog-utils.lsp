;;; ADDS Dialog Utilities

(defun adds-show-main-menu (/ dcl-id result)
  (setq dcl-id (load_dialog "adds-main-menu.dcl"))
  (if (not (new_dialog "adds_main_menu" dcl-id))
    (progn (alert "Cannot load ADDS menu!") (exit))
  )
  (action_tile "btn_draw_pipe"    "(done_dialog 1)")
  (action_tile "btn_draw_vessel"  "(done_dialog 2)")
  (action_tile "btn_place_pump"   "(done_dialog 3)")
  (action_tile "btn_place_hx"     "(done_dialog 4)")
  (action_tile "btn_route_pipe"   "(done_dialog 5)")
  (action_tile "btn_equipment_rpt" "(done_dialog 6)")
  (action_tile "btn_db_sync"      "(done_dialog 7)")
  (action_tile "btn_settings"     "(done_dialog 8)")
  (setq result (start_dialog))
  (unload_dialog dcl-id)
  result
)

(defun adds-show-settings (/ dcl-id result)
  (setq dcl-id (load_dialog "adds-main-menu.dcl"))
  (if (not (new_dialog "adds_settings" dcl-id))
    (progn (alert "Cannot load settings dialog!") (exit))
  )
  (set_tile "oracle_host" *ADDS-ORACLE-HOST*)
  (set_tile "oracle_port" (itoa *ADDS-ORACLE-PORT*))
  (set_tile "oracle_sid"  *ADDS-ORACLE-SID*)
  (set_tile "oracle_user" *ADDS-USER-NAME*)
  (action_tile "accept"
    "(setq *ADDS-ORACLE-HOST* (get_tile \"oracle_host\"))
     (setq *ADDS-ORACLE-PORT* (atoi (get_tile \"oracle_port\")))
     (setq *ADDS-ORACLE-SID* (get_tile \"oracle_sid\"))
     (setq *ADDS-USER-NAME* (get_tile \"oracle_user\"))
     (done_dialog 1)")
  (setq result (start_dialog))
  (unload_dialog dcl-id)
  result
)

(defun adds-dispatch-menu-result (choice)
  (cond
    ((= choice 1) (C:ADDS-DRAW-PIPE))
    ((= choice 2) (C:ADDS-DRAW-VESSEL))
    ((= choice 3) (C:ADDS-PLACE-PUMP))
    ((= choice 4) (C:ADDS-PLACE-HEAT-EXCHANGER))
    ((= choice 5) (C:ADDS-ROUTE-PIPE))
    ((= choice 6) (C:ADDS-EQUIPMENT-REPORT))
    ((= choice 7) (adds-db-flush-queue))
    ((= choice 8) (adds-show-settings))
    (T (princ "\nUnknown option."))
  )
)

(defun C:ADDS (/ choice)
  (adds-db-init)
  (setq choice (adds-show-main-menu))
  (if choice (adds-dispatch-menu-result choice))
)
